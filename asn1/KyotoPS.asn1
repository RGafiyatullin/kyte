KyotoPS DEFINITIONS ::= BEGIN
	-- ****** Primitives ******
	
	KPSCommandId ::= INTEGER (0..65535)
	KPSDbHandle ::= INTEGER (0..MAX)
    
    
    
	-- ****** PDUs ******
	
	-- PDU-type 0
	KPSBasicRequest ::= SEQUENCE {
		dbHandle KPSDbHandle
	}

	-- PDU-type 1
	KPSBasicResponse ::= SEQUENCE {
		rc INTEGER,
		errorDescription OCTET STRING OPTIONAL
	}

	-- PDU-type 2
	KPSSetOptionRequest ::= SEQUENCE {
		optCode INTEGER,

		optValueString OCTET STRING OPTIONAL,
		optValueInteger INTEGER (0..MAX) OPTIONAL
	}

	-- PDU-type 3
	KPSSetOptionResponse ::= KPSBasicResponse

	-- PDU-type 4
	KPSDbOpenRequest ::= SEQUENCE {
		dbFile OCTET STRING
	}

	-- PDU-type 5
	KPSDbOpenResponse ::= SEQUENCE {
		rc INTEGER,
		errorDescription OCTET STRING OPTIONAL,

		dbHandle KPSDbHandle OPTIONAL
	}

	-- PDU-type 6
	KPSDbCloseRequest ::= KPSBasicRequest

	--- PDU-type 7
	KPSDbCloseResponse ::= KPSBasicResponse

	-- PDU-type 8
	KPSDbClearRequest ::= KPSBasicRequest

	-- PDU-type 9
	KPSDbClearResponse ::= KPSBasicResponse

	-- PDU-type 10
	KPSDbCountRequest ::= KPSBasicRequest

	-- PDU-type 11
	KPSDbCountResponse ::= SEQUENCE {
		rc INTEGER,
		errorDescription OCTET STRING OPTIONAL,

		count INTEGER(0..MAX) OPTIONAL
	}

	-- PDU-type 12
	KPSDbSizeRequest ::= KPSBasicRequest

	-- PDU-type 13
	KPSDbSizeResponse ::= SEQUENCE {
		rc INTEGER,
		errorDescription OCTET STRING OPTIONAL,

		size INTEGER(0..MAX) OPTIONAL
	}

	-- PDU-type 14
	KPSDbSetRequest ::= SEQUENCE {
		dbHandle  KPSDbHandle,
		key       OCTET STRING,
		value     OCTET STRING
	}

	-- PDU-type 15
	KPSDbSetResponse ::= KPSBasicResponse

	-- PDU-type 16
	KPSDbGetRequest ::= SEQUENCE {
		dbHandle  KPSDbHandle,
		key	      OCTET STRING
	}
	-- PDU-type 17
	KPSDbGetResponse ::= SEQUENCE {
		errorDescription OCTET STRING OPTIONAL,
		
		rc INTEGER,

		value OCTET STRING OPTIONAL
	}
	-- PDU-type 18
	KPSDbRemoveRequest ::= SEQUENCE {
		dbHandle  KPSDbHandle,
		key	      OCTET STRING
	}
	-- PDU-type 19
	KPSDbRemoveResponse ::= KPSBasicResponse

END
